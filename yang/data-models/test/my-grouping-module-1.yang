module my-grouping-module-1 {
  /* Delete all generated comments when finished */
  namespace "http://www.adtran.com/ns/yang/my-grouping-module-1";
  /* Prefix - make this shorter if possible */
  prefix my-grp-md-1;

  /* Imports */

  /* Includes */

  organization
    "Adtran, Inc.";

  contact
    "<http://www.adtran.com/>";

  description
    "<INSERT A DESCRIPTION OF THE OVERALL INTENTION OF THE MODEL>

     Copyright (c) 2023 Adtran, Inc.  All rights reserved.";

  revision 2023-06-23 {
    description
      "Initial revision.";
    reference
      "None.";
  }

  /* Features */

  /* Identities */

  /* Typedefs */

  /* Groupings */
  grouping grouping-in-module-1 {
    description
      "Bla bla.";
    leaf a-leaf {
      type string;
      description
        "Bla bla bla.";
    }
  }

  /* Containers */

  /* RPCs */

  /* Notifications */

}
