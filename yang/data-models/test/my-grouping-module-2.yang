module my-grouping-module-2 {
  /* Delete all generated comments when finished */
  namespace "http://www.adtran.com/ns/yang/my-grouping-module-2";
  /* Prefix - make this shorter if possible */
  prefix my-grp-md-2;

  /* Imports */

  /* Includes */

  organization
    "Adtran, Inc.";

  contact
    "<http://www.adtran.com/>";

  description
    "<INSERT A DESCRIPTION OF THE OVERALL INTENTION OF THE MODEL>

     Copyright (c) 2023 Adtran, Inc.  All rights reserved.";

  revision 2023-06-23 {
    description
      "Initial revision.";
    reference
      "None.";
  }

  /* Features */

  /* Identities */

  /* Typedefs */

  /* Groupings */
  grouping grouping-in-module-2 {
    description
      "Bla bla.";
    leaf another-leaf {
      type string;
      description
        "Bla bla bla.";
    }
  }
  /* Containers */

  /* RPCs */

  /* Notifications */

}
