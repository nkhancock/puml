module test-submodules-sm1 {
  namespace "http://www.example.com/ns/yang/test-module-1";
  prefix tst-subs;
  revision 2023-11-09 {
    description
      "Initial revision.";
    reference
      "None.";
  }
}
