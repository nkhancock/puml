module my-uses-module-1 {
  /* Delete all generated comments when finished */
  namespace "http://www.adtran.com/ns/yang/my-uses-module-1";
  /* Prefix - make this shorter if possible */
  prefix my-uses-md-1;

  /* Imports */
  import my-grouping-module-1 {
    prefix my-grp-md;
  }
  /* Includes */

  organization
    "Adtran, Inc.";

  contact
    "<http://www.adtran.com/>";

  description
    "<INSERT A DESCRIPTION OF THE OVERALL INTENTION OF THE MODEL>

     Copyright (c) 2023 Adtran, Inc.  All rights reserved.";

  revision 2023-06-23 {
    description
      "Initial revision.";
    reference
      "None.";
  }

  /* Features */

  /* Identities */

  /* Typedefs */

  /* Groupings */

  /* Containers */
  container container-1 {
    description
      "A container.";
    uses my-grp-md:grouping-in-module-1;
  }
  /* RPCs */

  /* Notifications */

}
