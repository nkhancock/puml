module test-notifications {
  yang-version 1.1;
  namespace "http://www.example.com/ns/yang/test-notifications";
  prefix tst-nfc;
  revision 2023-07-21 {
    description
      "Initial revision.";
    reference
      "None.";
  }
  
  grouping notificatication-grouping {
    description
      "A grouping defining a notification.";
    notification grp-nfc {
      description
        "A notification in a list.";
      leaf binary-leaf {
        type binary;
        description
          "A leaf in a notification that is in a list.";
      }
    }
  }
  container container-a {
    description
      "A top-level container.";
    list list-a {
      key name;
      description
        "A list in a top-level container.";
      leaf name {
        type string;
        description
          "The name of the entry.";
      }
      notification list-a-nfc {
        description
          "A notification in a list.";
        leaf binary-leaf {
          type binary;
          description
            "A leaf in a notification that is in a list.";
        }
        container container-3 {
          description
            "A container in a notification that is in a list.";
          leaf another-leaf {
            type string;
            description
              "Just another leaf.";
          }
          leaf b-list-ref {
            type leafref {
              path 
                "/tst-nfc:container-b"
                + "/tst-nfc:list-b/tst-nfc:name";
            }
          }
        }
      }
    } 
  }
  container container-b {
    description
      "A another top-level container.";
    list list-b {
      key name;
      description
        "A list in a top-level container.";
      leaf name {
        type string;
        description
          "The name of the entry.";
      }
      uses notificatication-grouping;
    }
  }
  
  notification top-level-nfc {
    description
      "A top-level notification.";
    container container-4 {
      description
        "A container in a top-level notification.";
      leaf a-leaf {
        type uint32;
        description
          "Just a leaf.";
      }
      leaf list-b-ref {
        type leafref {
          path 
            "/tst-nfc:container-b"
            + "/tst-nfc:list-b/tst-nfc:name";
        }
      }
    }
    leaf just-a-leaf {
      type string;
      description
        "A leaf in a top-level notification.";
    }
  }
  
}
